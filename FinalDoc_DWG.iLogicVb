Imports Inventor
Imports System.Runtime.InteropServices
Imports System.IO



'exports all parts related to the currently open assembly, ignores parts in any subassemblies

Public Class ThisRule
    Private _DWGTranslator As TranslatorAddIn

    Sub Main()
        SetDWGTranslator()

        Dim doc As Document = ThisApplication.ActiveDocument

        Select Case doc.DocumentType
            Case DocumentTypeEnum.kPartDocumentObject
                ExportDWG(doc)
            Case DocumentTypeEnum.kAssemblyDocumentObject
                Dim asmDoc As AssemblyDocument = TryCast(doc, AssemblyDocument)
                ExportAssemblyDWGs(asmDoc.ComponentDefinition.Occurrences)

                ' Export the main assembly.
                ExportDWG(asmDoc)

            Case Else
                MessageBox.Show("This rule only supports Part and Assembly documents.")
                Exit Sub
        End Select
    End Sub

    'updates any holetables in a drawing (we need this right now because inventor sucks and our hole tables description column get messed up sometimes, if they ever fix it feel free to remove this)
    Private Sub UpdateHoleTables(doc As Document)
        If doc.DocumentType = DocumentTypeEnum.kDrawingDocumentObject Then
            Dim oDrawDoc As DrawingDocument = doc
            For Each oSheet As Sheet In oDrawDoc.Sheets
                For Each oTable As HoleTable In oSheet.HoleTables
                    For Each col As HoleTableColumn In oTable.HoleTableColumns
                        If col.Title = "HOLE" Then
                            Try
                                col.Title = "hole"
                                col.Title = "HOLE"
                            Catch ex As Exception
                                ' Ignore errors and continue to next column.
                            End Try
                        End If
                    Next
                Next
            Next
        End If
    End Sub

    Private Sub ExportAssemblyDWGs(occurrences As ComponentOccurrences)
        For Each oOcc As ComponentOccurrence In occurrences
            ' Check if it's a part with a normal BOM structure or an assembly with a normal BOM structure
            If oOcc.BOMStructure = BOMStructureEnum.kNormalBOMStructure Then
                ' If it's a part, export it.
                If oOcc.DefinitionDocumentType = DocumentTypeEnum.kPartDocumentObject Then
                    Dim oPartDoc As PartDocument = TryCast(oOcc.Definition.Document, PartDocument)
                    If oPartDoc IsNot Nothing Then
                        ExportDWG(oPartDoc)
                    End If
                End If
                ' If it's a phantom assembly, check its components but skip exporting the assembly itself.
            ElseIf oOcc.BOMStructure = BOMStructureEnum.kPhantomBOMStructure Then
                ExportAssemblyDWGs(oOcc.SubOccurrences) ' Recursive call to export phantom assembly components
            End If
        Next
    End Sub

    Private Sub ExportDWG(doc As Document)
        Dim oDrawingDoc As String = FindDrawingFile(doc)
        If Not String.IsNullOrEmpty(oDrawingDoc) Then
            Dim oDWG As Document = ThisApplication.Documents.Open(oDrawingDoc, True)
			 oDWG.Update()
            SaveCopyAsDWG(oDWG)
            oDWG.Close(True)
        End If
    End Sub

    Private Sub SetDWGTranslator()
        For Each oAddIn As ApplicationAddIn In ThisApplication.ApplicationAddIns
            If oAddIn.ClassIdString = "{C24E3AC2-122E-11D5-8E91-0010B541CD80}" Then
                _DWGTranslator = oAddIn
                Exit Sub
            End If
        Next
        Throw New Exception("Could not access DWG translator.")
    End Sub

    Private Function FindDrawingFile(PartOrAssemblyDoc As Document) As String
        Dim fullFilename As String = PartOrAssemblyDoc.FullFileName
        Dim Path As String = System.IO.Path.GetFullPath(fullFilename)
        Dim filename As String = System.IO.Path.GetFileNameWithoutExtension(fullFilename)
        Dim drawingFilename As String = ThisApplication.DesignProjectManager.ResolveFile(Path, filename & ".idw")
        If drawingFilename = "" Then
            Return ""
        Else
            Return drawingFilename
        End If
    End Function

    Private Sub SaveCopyAsDWG(doc As Document)
        UpdateHoleTables(doc)
        Dim oOptions As NameValueMap = ThisApplication.TransientObjects.CreateNameValueMap
        Dim oContext As TranslationContext = ThisApplication.TransientObjects.CreateTranslationContext
        oContext.Type = IOMechanismEnum.kFileBrowseIOMechanism

        Dim dirPath As String = System.IO.Path.Combine(System.Environment.GetFolderPath(System.Environment.SpecialFolder.Desktop), "Exports")
        Dim fileName As String = System.IO.Path.Combine(dirPath, System.IO.Path.GetFileNameWithoutExtension(doc.FullFileName) & ".dwg")

        If Not System.IO.Directory.Exists(dirPath) Then
            System.IO.Directory.CreateDirectory(dirPath)
        End If

        If _DWGTranslator.HasSaveCopyAsOptions(doc, oContext, oOptions) Then
            oOptions.Value("Export_Acad_Version") = 4
            oOptions.Value("Multi_Sheet") = 0
            oOptions.Value("Replace_Fonts") = True

            Dim oDataMedium As DataMedium = ThisApplication.TransientObjects.CreateDataMedium
            oDataMedium.FileName = fileName
            _DWGTranslator.SaveCopyAs(doc, oContext, oOptions, oDataMedium)
        End If
    End Sub
End Class
