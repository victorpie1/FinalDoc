Imports System.IO
Imports Inventor
Imports System.Runtime.InteropServices

'Run this at the highest level assembly for the project you want to export.
'places a FinalDoc folder on your desktop
'it will tell you "export complete" when done, you can do other stuff on your computer while it runs, be careful about running to many applications as this thing is RAM intensive
'it automatically creates a folder for .stp and .dwg files
'if a file isnt exporting, please make sure the part/assembly isnt set to purchased/ref/phantom. ONLY normal parts and assemblys will get .dwg files

Public Class ThisRule
    ' Variables to hold the translators
    Private _DWGTranslator As TranslatorAddIn
    Private _STEPTranslator As TranslatorAddIn

    Public Sub Main()
        ' Get the application object
        Dim app As Inventor.Application = ThisApplication

        ' Initialize the translators
        SetDWGTranslator()
        SetSTEPTranslator()

        ' Get the main assembly document
        Dim mainAssembly As AssemblyDocument = app.ActiveDocument

        ' Create HashSets to track processed subassemblies and parts
        Dim processedSubAssemblies As New HashSet(Of String)
        Dim processedParts As New HashSet(Of String)

        ' Call the ProcessAssembly subroutine for the main assembly
        ProcessAssembly(mainAssembly, "", processedSubAssemblies, processedParts, , , False)

        MessageBox.Show("Export Complete")
    End Sub

    ' The ProcessAssembly subroutine recursively processes the main assembly and its subassemblies.
    ' It creates output folders for each assembly and part, and exports .stp and .dwg files.
Public Sub ProcessAssembly(assembly As AssemblyDocument, baseFolder As String, processedSubAssemblies As HashSet(Of String), processedParts As HashSet(Of String), Optional cadFolder As String = Nothing, Optional drawingsFolder As String = Nothing, Optional closeAssembly As Boolean = False)
    ' Get the part number
    Dim fullPartNumber As String = assembly.PropertySets.Item("Design Tracking Properties").Item("Part Number").Value.ToString()
    Dim partNumber As String = fullPartNumber.Split(":")(0)

    ' Check if the assembly has already been processed
    If processedSubAssemblies.Contains(partNumber) Then
        Return
    End If

    ' Create a directory on the desktop if this is the main assembly
    If String.IsNullOrEmpty(baseFolder) Then
        baseFolder = System.IO.Path.Combine(System.Environment.GetFolderPath(System.Environment.SpecialFolder.Desktop), partNumber.Substring(0, 4) & " Final Doc")
    End If

    ' Create the CAD and Drawings directories for the current assembly
    If String.IsNullOrEmpty(cadFolder) Or String.IsNullOrEmpty(drawingsFolder) Or partNumber.Length <= 10 Then
        cadFolder = System.IO.Path.Combine(baseFolder, "CAD", partNumber)
        drawingsFolder = System.IO.Path.Combine(baseFolder, "Drawings", partNumber)
        Directory.CreateDirectory(cadFolder)
        Directory.CreateDirectory(drawingsFolder)
    End If

    ' Process the subassemblies recursively
    For Each subAssembly As ComponentOccurrence In assembly.ComponentDefinition.Occurrences
        ' Skip suppressed components
        If subAssembly.Suppressed Then
            Continue For
        End If

        ' Check if it's a normal or inseparable BOM structure
        If (subAssembly.BOMStructure = BOMStructureEnum.kNormalBOMStructure Or subAssembly.BOMStructure = BOMStructureEnum.kInseparableBOMStructure) And TypeOf subAssembly.Definition.Document Is AssemblyDocument Then
            ' Handle inseparable components differently
            If subAssembly.BOMStructure = BOMStructureEnum.kInseparableBOMStructure Then
                ' Export the drawing of the inseparable component to the current assembly's folder
                Dim inseparablePart As Document = subAssembly.Definition.Document
                ExportDWG(inseparablePart, drawingsFolder)
                ' Skip processing parts within the inseparable assembly
                Continue For
            End If

            ' Handle normal assemblies
            Dim subAssemblyDoc As AssemblyDocument = ThisApplication.Documents.Open(subAssembly.ReferencedDocumentDescriptor.ReferencedFileDescriptor.FullFileName, True)
            Dim subCadFolder As String = If(subAssemblyDoc.PropertySets.Item("Design Tracking Properties").Item("Part Number").Value.ToString().Length > 10, cadFolder, Nothing)
            Dim subDrawingsFolder As String = If(subAssemblyDoc.PropertySets.Item("Design Tracking Properties").Item("Part Number").Value.ToString().Length > 10, drawingsFolder, Nothing)
            ProcessAssembly(subAssemblyDoc, baseFolder, processedSubAssemblies, processedParts, subCadFolder, subDrawingsFolder, True)

        ' Handle phantom assemblies
        ElseIf subAssembly.BOMStructure = BOMStructureEnum.kPhantomBOMStructure Then
            ExportPartFiles(subAssembly.Definition.Document, cadFolder, drawingsFolder, processedParts)
        End If
    Next

    ' After processing subassemblies, export the files for the main assembly
    assembly.Activate()
    assembly.Update()
    ExportPartFiles(assembly, cadFolder, drawingsFolder, processedParts)

    If Not processedParts.Contains(assembly.DisplayName) Then
        ExportDWG(assembly, drawingsFolder)
        ExportStep(assembly, cadFolder)
        processedParts.Add(assembly.DisplayName)
    End If

    processedSubAssemblies.Add(partNumber)

    If closeAssembly Then
        assembly.Close(True)
    End If
End Sub




'it just renames one of the columns in the hole table and sets it back to the original name. 
'We need this because inventor sucks with hole tables, if one day opening a drawing doesnt break hole tables, feel free to remove this.
Private Sub UpdateHoleTables(doc As Document)
    If doc.DocumentType = DocumentTypeEnum.kDrawingDocumentObject Then
        Dim oDrawDoc As DrawingDocument = doc
        For Each oSheet As Sheet In oDrawDoc.Sheets
            For Each oTable As HoleTable In oSheet.HoleTables
                For Each col As HoleTableColumn In oTable.HoleTableColumns
                    If col.Title = "HOLE" Then
                        Try
                            col.Title = "hole"
                            col.Title = "HOLE"
                        Catch ex As Exception
                            ' Ignore errors and continue to next column.
                        End Try
                    End If
                Next
            Next
        Next
    End If
End Sub

' The ExportAssemblyDWGs subroutine exports .dwg files for all normal parts in the given occurrences.
Private Sub ExportAssemblyDWGs(occurrences As ComponentOccurrences, dirPath As String)
    For Each oOcc As ComponentOccurrence In occurrences
        ' Check if it's a part with a normal BOM structure or an assembly with a normal BOM structure
        If oOcc.BOMStructure = BOMStructureEnum.kNormalBOMStructure Then
            ' If it's a part, export it.
            If oOcc.DefinitionDocumentType = DocumentTypeEnum.kPartDocumentObject Then
                Dim oPartDoc As PartDocument = TryCast(oOcc.Definition.Document, PartDocument)
                If oPartDoc IsNot Nothing Then
                    ExportDWG(oPartDoc, dirPath)
                    ExportStep(oPartDoc, dirPath)
                End If
            End If
        End If
    Next
End Sub

' The ExportPartFiles subroutine exports .dwg files for all parts in the given assembly.
Public Sub ExportPartFiles(assembly As AssemblyDocument, cadFolder As String, drawingsFolder As String, processedParts As HashSet(Of String))
    For Each occurrence As ComponentOccurrence In assembly.ComponentDefinition.Occurrences
        ' Skip suppressed components
        If occurrence.Suppressed Then
            Continue For
        End If

        ' Check if it's a normal or inseparable BOM structure
        If (occurrence.BOMStructure = BOMStructureEnum.kNormalBOMStructure Or occurrence.BOMStructure = BOMStructureEnum.kInseparableBOMStructure) And TypeOf occurrence.Definition.Document Is PartDocument Then
            Dim part As PartDocument = occurrence.Definition.Document
            Dim partNumber As String = part.PropertySets.Item("Design Tracking Properties").Item("Part Number").Value.ToString().Split(":")(0)

            If processedParts.Contains(partNumber) Then
                Continue For
            End If

            ExportDWG(part, drawingsFolder)
            processedParts.Add(partNumber)
        End If
    Next
End Sub


'calls the find drawing file function, and then sends the correct drawing file to be opened by the SaveCopyAsDWG function
Private Sub ExportDWG(doc As Document, dirPath As String)
    Dim oDrawingDoc As String = FindDrawingFile(doc)
    If Not String.IsNullOrEmpty(oDrawingDoc) Then
        Dim oDWG As Document = ThisApplication.Documents.Open(oDrawingDoc, True)
        oDWG.Update()
        SaveCopyAsDWG(oDWG, dirPath)
        oDWG.Close(True)
    End If
End Sub

'Exports assemblys and .stp files, and organizes them into the CAD folder, DOES NOT export parts as .stp's
Private Sub ExportStep(doc As Document, dirPath As String)
    Dim oOptions As NameValueMap = ThisApplication.TransientObjects.CreateNameValueMap
    Dim oContext As TranslationContext = ThisApplication.TransientObjects.CreateTranslationContext
    ' Set the output directory path and the filename.

 Dim fileName As String = System.IO.Path.Combine(dirPath, System.IO.Path.GetFileNameWithoutExtension(doc.FullFileName) & ".stp")

    Try
        ' If the output directory doesn't exist, create it.
        If Not System.IO.Directory.Exists(dirPath) Then
            System.IO.Directory.CreateDirectory(dirPath)
        End If

        ' If the STEP Translator supports the document, export it.
        If _STEPTranslator.HasSaveCopyAsOptions(doc, oContext, oOptions) Then
            oOptions.Value("ApplicationProtocolType") = 3
            oContext.Type = IOMechanismEnum.kFileBrowseIOMechanism
            Dim oData As DataMedium = ThisApplication.TransientObjects.CreateDataMedium
            oData.FileName = fileName
            _STEPTranslator.SaveCopyAs(doc, oContext, oOptions, oData)
        End If
    Catch ex As Exception
        ' Show error message if there's an exception.
        MessageBox.Show(String.Format("Error exporting {0}: {1}", doc.DisplayName, ex.Message))
    End Try
End Sub

'idk I guess I need this to make the dwg translator work
Private Sub SetDWGTranslator()
    For Each oAddIn As ApplicationAddIn In ThisApplication.ApplicationAddIns
        If oAddIn.ClassIdString = "{C24E3AC2-122E-11D5-8E91-0010B541CD80}" Then
            _DWGTranslator = oAddIn
            Exit Sub
        End If
    Next
    Throw New Exception("Could not access DWG translator.")
End Sub
'idk I guess I need this to make the step translator work
Private Sub SetSTEPTranslator()
    For Each oAddIn As ApplicationAddIn In ThisApplication.ApplicationAddIns
        ' If the current AddIn is the STEP Translator, set it.
        If oAddIn.ClassIdString = "{90AF7F40-0C01-11D5-8E83-0010B541CD80}" Then
            _STEPTranslator = oAddIn
            Exit Sub
        End If
    Next

    ' If there's no STEP Translator, throw an exception.
    Throw New Exception("Could not access STEP translator.")
End Sub


'finds the drawing files associated with the parts/assembly
Private Function FindDrawingFile(PartOrAssemblyDoc As Document) As String
    Dim fullFilename As String = PartOrAssemblyDoc.FullFileName
    Dim Path As String = System.IO.Path.GetFullPath(fullFilename)
    Dim filename As String = System.IO.Path.GetFileNameWithoutExtension(fullFilename)
    Dim drawingFilename As String = ThisApplication.DesignProjectManager.ResolveFile(Path, filename & ".idw")
    If drawingFilename = "" Then
        Return ""
    Else
        Return drawingFilename
    End If
End Function


'The function that saves the currently open .idw as a .dwg
Private Sub SaveCopyAsDWG(doc As Document, dirPath As String)
    ' Define these variables outside the Try block
    Dim oOptions As NameValueMap = Nothing
    Dim oContext As TranslationContext = Nothing
    Dim oDataMedium As DataMedium = Nothing

    Try
        If doc Is Nothing Then
            MessageBox.Show("Document is not loaded correctly.")
            Return
        End If

        UpdateHoleTables(doc)
        oOptions = ThisApplication.TransientObjects.CreateNameValueMap
        oContext = ThisApplication.TransientObjects.CreateTranslationContext
        oContext.Type = IOMechanismEnum.kFileBrowseIOMechanism

        Dim fileName As String = System.IO.Path.Combine(dirPath, System.IO.Path.GetFileNameWithoutExtension(doc.FullFileName) & ".dwg")

        If Not System.IO.Directory.Exists(dirPath) Then
            MessageBox.Show("Directory does not exist, creating directory.")
            System.IO.Directory.CreateDirectory(dirPath)
        End If

        If _DWGTranslator.HasSaveCopyAsOptions(doc, oContext, oOptions) Then
            oOptions.Value("Export_Acad_Version") = 4
            oOptions.Value("Multi_Sheet") = 0
            oOptions.Value("Replace_Fonts") = True

            oDataMedium = ThisApplication.TransientObjects.CreateDataMedium
            oDataMedium.FileName = fileName

            _DWGTranslator.SaveCopyAs(doc, oContext, oOptions, oDataMedium)
        Else
            MessageBox.Show("Translator does not support SaveCopyAs for this document.")
        End If
    Catch ex As Exception
        ' Display inputs in message box only when an error occurs
       ' If Not (oOptions Is Nothing Or oContext Is Nothing Or oDataMedium Is Nothing) Then
         '   MessageBox.Show(String.Format("Inputs to SaveCopyAs: Document={0}, Context={1}, Options=Export_Acad_Version:{2}, Multi_Sheet:{3}, Replace_Fonts:{4}, DataMedium={5}", doc.FullDocumentName, oContext.Type, oOptions.Value("Export_Acad_Version"), oOptions.Value("Multi_Sheet"), oOptions.Value("Replace_Fonts"), oDataMedium.FileName))
       ' End If
       ' MessageBox.Show("An error occurred: " & ex.Message)
    End Try
End Sub




End Class
